# Ontology
A set of classes to build ontologies.
- Rights: Creative Commons 4.0 CC BY-SA, https://creativecommons.org/licenses/by-sa/4.0/

## My Ontology (SpecIF:Heading)
- dcterms:type: W3C:Ontology

## Introduction (SpecIF:Heading)
- dcterms:description: An Ontology collects terms used in a certain domain. Agreed-upon terms help both collaborators to communicate more clearly and systems to match data fields automatically.
  All terms carry a namespace, which is the first part separated with ':' or '.' ― they are thus easily recognized in text and data fields. For display, systems may choose to replace the ontology terms by words used in the domain or national language.
  The terms have a lifecycle status as follows:
  - experimental: The term is being used in first projects, but has not yet any normative maturity.
  - submitted: The term has been submitted for adoption.
  - released: The term has been adopted for use and is preferred among equivalent terms.
  - equivalent: The term has been adopted for use, but the released term is preferred.
  - deprecated: The term shall not any more be used; use a released term.

## Namespaces (SpecIF:Heading)
- dcterms:description: A 'Namespace' is a is a set of signs (names) that are used to identify and refer to objects of various kinds. A namespace ensures that all of a given set of objects have unique names so that they can be easily identified. (Source: Wikipedia)
  The value specified for SpecIF:Origin is used as namespace prefix in linked data and must thus be an URL or URI.

## Entity Class Terms (SpecIF:Heading)
- dcterms:description: An entity represents an artefact, e.g. a model element or a requirement. The terms listed in this chapter may be used to distinguish different classes (types) of artefacts constituting a system specification. An entity may serve as subject or as object in a subject-predicate-object statement. Each entity class may define an individual set of properties for carrying the information 'payload'.
  An entity class corresponds to a 'SPEC-OBJECT-TYPE' and an entity is a 'SPEC-OBJECT' in the Requirements Interchange Format (ReqIF). In ArchiMate® 3.0, an entity is an Element.

## Relationship Class Terms (SpecIF:Heading)
- dcterms:description: A relationship represents a logic affinity or association between two entities, i.e. system specification artefacts. The terms listed in this chapter may be used as predicates to distinguish different classes (types) of relationships. Each relationship class may define an individual set of properties for carrying the information 'payload'.
  For each predicate (relationship class), a list of eligible entity classes may be defined for subjects and objects, respectively. For example, the predicate [[oslc_rm:satisfies]] is usually confined to [[FMC:Actor]] and [[FMC:State]] as subject and [[IREB:Requirement]] as object.
  A relationship consisting of subject-predicate-object (where an entity may serve as subject or object) can be directly mapped to a ReqIF relation, a RDF triple in OSLC or 'linked data' in general.
  A relationship class corresponds to a 'SPEC-RELATION-TYPE' and a relationship is a 'SPEC-RELATION' in the Requirements Interchange Format (ReqIF). In ArchiMate® 3.0, a relationship is also a Relationship.

## Property Class Terms (SpecIF:Heading)
- dcterms:description: A property carries information 'payload' and may be applied to entities or relationships. The terms listed in this chapter are used as property name/title, whereas the information is provided as 'value'. Usually a combination of complimentary properties is used per entity or relationship class.
  A property class corresponds to an 'ATTRIBUTE-DEFINITION' and a property is an 'ATTRIBUTE-VALUE' in the Requirements Interchange Format (ReqIF).

## Property Value Terms (SpecIF:Heading)
- dcterms:description: These are terms for certain enumerated property values. Not only the property titles, but also any enumerated value must be mapped between different systems or domains; therefore using defined terms is beneficial. Of course, like any other vocabulary term, a term used as property value for transmission or storage can be translated for display.
