# Library Ontology (Example)
An ontology for libraries.
- Rights: Creative Commons 4.0 CC BY-SA, https://creativecommons.org/licenses/by-sa/4.0/

## Library Ontology (SpecIF:Heading)
- dcterms:description: An example ontology with library, book and related terms.
- dcterms:type: W3C:Ontology

## Introduction (SpecIF:Heading)
- dcterms:description: An Ontology collects terms used in a certain domain. Agreed-upon terms help both collaborators to communicate more clearly and systems to match data fields automatically.
  All terms carry a namespace, which is the first part separated with ':' or '.' ― they are thus easily recognized in text and data fields. For display, systems may choose to replace the ontology terms by words used in the domain or national language.
  The terms have a lifecycle status as follows:
  - experimental: The term is being used in first projects, but has not yet any normative maturity.
  - submitted: The term has been submitted for adoption.
  - released: The term has been adopted for use and is preferred among equivalent terms.
  - equivalent: The term has been adopted for use, but the released term is preferred.
  - deprecated: The term shall not any more be used; use a released term.

## Namespaces (SpecIF:Heading)
- dcterms:description: A 'Namespace' is a is a set of signs (names) that are used to identify and refer to objects of various kinds. A namespace ensures that all of a given set of objects have unique names so that they can be easily identified. (Source: Wikipedia)
  The value specified for SpecIF:Origin is used as namespace prefix in linked data and must thus be an URL or URI.

## exlib: (SpecIF:Namespace)
- dcterms:description: The namespace for a library ontology used for an example.
- SpecIF:Home: https://example-library.org#

## rdf: (SpecIF:Namespace)
- SpecIF:Home: http://www.w3.org/1999/02/22-rdf-syntax-ns#

## rdfs: (SpecIF:Namespace)
- SpecIF:Home: http://www.w3.org/2000/01/rdf-schema#

## owl: (SpecIF:Namespace)
- SpecIF:Home: http://www.w3.org/2002/07/owl#

## sh: (SpecIF:Namespace)
- dcterms:description: Namespace of RDF shapes.
- SpecIF:Home: https://www.w3.org/ns/shacl

## xs: (SpecIF:Namespace)
- SpecIF:Home: http://www.w3.org/2001/XMLSchema#

## dcterms: (SpecIF:Namespace)
- SpecIF:Home: http://purl.org/dc/terms/

## foaf: (SpecIF:Namespace)
- dcterms:description: FOAF is a project devoted to linking people and information using the Web. Regardless of whether information is in people's heads, in physical or digital documents, or in the form of factual data, it can be linked. FOAF integrates three kinds of network: social networks of human collaboration, friendship and association; representational networks that describe a simplified view of a cartoon universe in factual terms, and information networks that use Web-based linking to share independently published descriptions of this inter-connected world. FOAF does not compete with socially-oriented Web sites; rather it provides an approach in which different sites can tell different parts of the larger story, and by which users can retain some control over their information in a non-proprietary format.
- SpecIF:Home: http://xmlns.com/foaf/spec/#

## schema: (SpecIF:Namespace)
- dcterms:description: 'Schema.org' is a collaborative, community activity with a mission to create, maintain, and promote schemas for structured data on the Internet, on web pages, in email messages, and beyond.
- SpecIF:Home: https://schema.org#

## SpecIF: (SpecIF:Namespace)
- dcterms:description: The Specification Integration Facility (SpecIF) integrates partial system models from different methods and tools in a semantic net. Collaborators shall browse, search and audit engineering results in a common context. Also, the exchange of model information between organizations and tools is facilitated. SpecIF represents the visible, i.e. the diagrams and the text, as well as the semantics of system specifications.
- SpecIF:Home: https://specif.de/v1.2/schema#

## W3C: (SpecIF:Namespace)
- dcterms:description: The World Wide Web Consortium (W3C) is the main international standards organization for the World Wide Web. Founded in 1994 and led by Tim Berners-Lee, the consortium is made up of member organizations that maintain full-time staff working together in the development of standards for the World Wide Web. W3C also engages in education and outreach, develops software and serves as an open forum for discussion about the Web. *(Source: [Wikipedia](https://en.wikipedia.org/wiki/World_Wide_Web_Consortium))*
- SpecIF:Home: https://www.w3.org/standards/semanticweb#

## Entity Class Terms (SpecIF:Heading)
- dcterms:description: An entity represents an artefact, e.g. a model element or a requirement. The terms listed in this chapter may be used to distinguish different classes (types) of artefacts constituting a system specification. An entity may serve as subject or as object in a subject-predicate-object statement. Each entity class may define an individual set of properties for carrying the information 'payload'.
  An entity class corresponds to a 'SPEC-OBJECT-TYPE' and an entity is a 'SPEC-OBJECT' in the Requirements Interchange Format (ReqIF). In ArchiMate® 3.0, an entity is an Element.

## exlib:Library (SpecIF:TermResourceClass)
- SpecIF:Revision: v0.4
- dcterms:description: Term used for libraries in the example.
- SpecIF:TermStatus: SpecIF:LifecycleStatusReleased
- SpecIF:LocalTerm: Library
- SpecIF:LocalTermPlural: Libraries
- SpecIF:Icon: ⌂
- SpecIF:isHeading: false
- SpecIF:Instantiation: SpecIF:InstantiationUser

## exlib:Book (SpecIF:TermResourceClass)
- SpecIF:Revision: vo.4
- dcterms:description: In the example, the term used for books. Editions are represented, not the individuals.
- SpecIF:TermStatus: SpecIF:LifecycleStatusReleased
- SpecIF:LocalTerm: Book
- SpecIF:LocalTermPlural: Books
- SpecIF:Icon: 🗏
- SpecIF:isHeading: false
- SpecIF:Instantiation: SpecIF:InstantiationUser

## exlib:Author (SpecIF:TermResourceClass)
- SpecIF:Revision: v0.4
- dcterms:description: Term used for book authors in the example.
- SpecIF:TermStatus: SpecIF:LifecycleStatusReleased
- SpecIF:LocalTerm: Author
- SpecIF:LocalTermPlural: Authors
- SpecIF:Icon: ✎
- SpecIF:isHeading: false
- SpecIF:Instantiation: SpecIF:InstantiationUser

## SpecIF:Folder (SpecIF:TermResourceClass)
- dcterms:identifier: RC-Folder
- SpecIF:Revision: 1.1
- dcterms:description: A 'Folder' may appear at any level with optional description.
- SpecIF:TermStatus: SpecIF:LifecycleStatusReleased
- SpecIF:LocalTerm: Folder
- SpecIF:LocalTermPlural: Folders
- SpecIF:isHeading: true
- SpecIF:Instantiation: SpecIF:InstantiationUser

## Relationship Class Terms (SpecIF:Heading)
- dcterms:description: A relationship represents a logic affinity or association between two entities, i.e. system specification artefacts. The terms listed in this chapter may be used as predicates to distinguish different classes (types) of relationships. Each relationship class may define an individual set of properties for carrying the information 'payload'.
  For each predicate (relationship class), a list of eligible entity classes may be defined for subjects and objects, respectively. For example, the predicate [[oslc_rm:satisfies]] is usually confined to [[FMC:Actor]] and [[FMC:State]] as subject and [[IREB:Requirement]] as object.
  A relationship consisting of subject-predicate-object (where an entity may serve as subject or object) can be directly mapped to a ReqIF relation, a RDF triple in OSLC or 'linked data' in general.
  A relationship class corresponds to a 'SPEC-RELATION-TYPE' and a relationship is a 'SPEC-RELATION' in the Requirements Interchange Format (ReqIF). In ArchiMate® 3.0, a relationship is also a Relationship.

## exlib:owned-by (SpecIF:TermStatementClass)
- SpecIF:Revision: 0.4
- dcterms:description: A relation to express that a book is owned by a library.
- SpecIF:TermStatus: SpecIF:LifecycleStatusReleased
- SpecIF:LocalTerm: owned by
- SpecIF:isUndirected: false
- SpecIF:Instantiation: SpecIF:InstantiationUser

## exlib:written-by (SpecIF:TermStatementClass)
- SpecIF:Revision: 0.4
- dcterms:description: A relation to express that a book is written by an author.
- SpecIF:TermStatus: SpecIF:LifecycleStatusReleased
- SpecIF:LocalTerm: written by
- SpecIF:isUndirected: false
- SpecIF:Instantiation: SpecIF:InstantiationUser

## Property Class Terms (SpecIF:Heading)
- dcterms:description: A property carries information 'payload' and may be applied to entities or relationships. The terms listed in this chapter are used as property name/title, whereas the information is provided as 'value'. Usually a combination of complimentary properties is used per entity or relationship class.
  A property class corresponds to an 'ATTRIBUTE-DEFINITION' and a property is an 'ATTRIBUTE-VALUE' in the Requirements Interchange Format (ReqIF).

## dcterms:title (SpecIF:TermPropertyClassString)
- dcterms:identifier: PC-Name
- SpecIF:Revision: 1.1
- dcterms:description: A name given to the resource. (source: DCMI)
  Title (reference: Dublin Core) of the resource represented as rich text in XHTML content. SHOULD include only content that is valid inside an XHTML 'span' element. (source: OSLC)
- SpecIF:TermStatus: SpecIF:LifecycleStatusReleased
- SpecIF:LocalTerm: Title
- SpecIF:isRequired: false
- SpecIF:multiple: false
- SpecIF:singleLanguage: false
- SpecIF:StringMaxLength: 256

## dcterms:description (SpecIF:TermPropertyClassString)
- dcterms:identifier: PC-Description
- SpecIF:Revision: 1.1
- dcterms:description: An account of the resource. (source: DCMI)
  Descriptive text (reference: Dublin Core) about resource represented as rich text in XHTML content. SHOULD include only content that is valid and suitable inside an XHTML 'div' element. (source: OSLC)
- SpecIF:TermStatus: SpecIF:LifecycleStatusReleased
- SpecIF:LocalTerm: Description
- SpecIF:isRequired: false
- SpecIF:multiple: false
- SpecIF:singleLanguage: false

## exlib:Location (SpecIF:TermPropertyClassString)
- SpecIF:Revision: 0.4
- dcterms:description: The geographic location.
- SpecIF:TermStatus: SpecIF:LifecycleStatusReleased
- SpecIF:LocalTerm: Location
- SpecIF:isRequired: false
- SpecIF:multiple: false
- SpecIF:singleLanguage: false
- SpecIF:StringMaxLength: 256

## exlib:ISBN (SpecIF:TermPropertyClassString)
- SpecIF:Revision: 0.4
- dcterms:description: The International Standard Book Number (ISBN) is a numeric commercial book identifier that is intended to be unique. Publishers purchase or receive ISBNs from an affiliate of the International ISBN Agency. Source: [Wikipedia](https://en.wikipedia.org/wiki/ISBN)
- SpecIF:TermStatus: SpecIF:LifecycleStatusReleased
- SpecIF:isRequired: true
- SpecIF:multiple: false
- SpecIF:singleLanguage: false
- SpecIF:TextFormat: SpecIF:TextFormatPlain
- SpecIF:StringMaxLength: 32

## Property Value Terms (SpecIF:Heading)
- dcterms:description: These are terms for certain enumerated property values. Not only the property titles, but also any enumerated value must be mapped between different systems or domains; therefore using defined terms is beneficial. Of course, like any other vocabulary term, a term used as property value for transmission or storage can be translated for display.

## Statements
- exlib:Library SpecIF:hasProperty dcterms:title
- exlib:Library SpecIF:hasProperty dcterms:description
- exlib:Book SpecIF:hasProperty dcterms:title
- exlib:Book SpecIF:hasProperty dcterms:description
- exlib:Author SpecIF:hasProperty dcterms:title
- exlib:Author SpecIF:hasProperty dcterms:description
- exlib: SpecIF:isNamespace exlib:Library
- exlib: SpecIF:isNamespace exlib:Book
- exlib: SpecIF:isNamespace exlib:Author
- dcterms: SpecIF:isNamespace dcterms:title
- dcterms: SpecIF:isNamespace dcterms:description
- SpecIF:Folder SpecIF:hasProperty dcterms:title
- SpecIF:Folder SpecIF:hasProperty dcterms:description
- SpecIF: SpecIF:isNamespace SpecIF:Folder
- exlib:Library SpecIF:hasProperty exlib:Location
- exlib: SpecIF:isNamespace exlib:owned-by
- exlib:Book SpecIF:isEligibleAsSubject exlib:owned-by
- exlib:Library SpecIF:isEligibleAsObject exlib:owned-by
- exlib: SpecIF:isNamespace exlib:written-by
- exlib:Book SpecIF:isEligibleAsSubject exlib:written-by
- exlib:Author SpecIF:isEligibleAsObject exlib:written-by
- exlib:Book SpecIF:hasProperty exlib:ISBN
