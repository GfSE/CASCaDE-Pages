# Libraries (Example)
An ontology-based data-set with libraries, their books and authors.
- Rights: Creative Commons 4.0 CC BY-SA, https://creativecommons.org/licenses/by-sa/4.0/

## Libraries (SpecIF:Heading)

## Bibliothèque nationale de France (BnF) (exlib:Library)
- exlib:Location: Paris

## Books (SpecIF:Heading)

## Le Malade (exlib:Book)

## Les petits enfants du siecle (exlib:Book)
- dcterms:description: Jo de Bagnolet " est née des allocations et d'un jour férié dont la matinée s'étirait, bienheureuse ".
  Dix enfants vont suivre, apportant en prime à leurs parents la machine à laver, le Frigidaire, la télé, la voiture et le prix Cognac ! Josyane les élèvera tous. Ses seules distractions : les courses et ses devoirs le soir sur la table de cuisine. Ses seuls amis, Nicolas, le petit frère qui comprend tout et Guido, le maçon italien, né sur les collines. L'amour de Guido bouleverse la vie de Josyane, il en chasse toute la laideur et la bêtise.
  Christine Rochefort fait ici un tableau criant de vérité des grands ensembles, de ces blocs illuminés la nuit, en plein ciel, si gris le jour, le béton cachant mal la pauvreté. Elle dit, admirablement et avec beaucoup d'humour, le mal de vivre à Bagnolet, à Sarcelles et autres lieux de même type, sans âme et sans arbres. Une oeuvre très forte du célèbre auteur du Repos du guerrier et des Stances à Sophie.
  Source. [Sens Critique](https://www.senscritique.com/)

## Authors (SpecIF:Heading)

## Victor Hugo (exlib:Author)

## Christiane Rochefort (exlib:Author)

## Statements
- Le Malade exlib:owned-by Bibliothèque nationale de France (BnF)
- Le Malade exlib:written-by Victor Hugo
